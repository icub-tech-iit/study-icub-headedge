# eyes_functional_requirements

## EyesFR_1: Kinematics (Container)

### EyesFR_2: Range of motion (Functional)
The eye bulbs must guarantee the range of motion (tilt, pan) of the head Mk 2.
- Tilt: [-30 30] deg
- Pan: [-68 68] deg

### EyesFR_3: Velocity (Functional)
The eye bulbs must guarantee to reach the maximum velocities (tilt, pan) of the head Mk 2.
- Tilt: FIXME
- Pan: FIXME
