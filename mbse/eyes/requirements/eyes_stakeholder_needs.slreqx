# eyes_stakeholder_needs

## EyesSN_1: Robustness (Container)

### EyesSN_2: Wiring static robustness (Functional)
Wiring must not break or unplug when eyes cover their entire RoM.

### EyesSN_3: Wiring dynamic robustness (Functional)
This requirement refines EyesSN_2 in that we must guarantee that the wiring remains robust in all dynamic operating conditions of the eyes:
- Eye bulbs move covering all the possible characteristic velocities of the mechanism.

## EyesSN_4: Kinematics (Container)

### EyesSN_5: Range of motion (Functional)
The eye bulbs must guarantee the range of motion (tilt, pan) of the head Mk 2.
- Tilt: [-30 30] deg
- Pan: [-68 68] deg

### EyesSN_6: Velocity (Functional)
The eye bulbs must guarantee to reach the maximum velocities (tilt, pan) of the head Mk 2.

## EyesSN_7: Camera performance (Container)
As a reference, see https://icub-tech-iit.github.io/documentation/upgrade_kits/head_4k/support/.

### EyesSN_8: Camera resolution (Functional)
The new cameras must guarantee 4k resolution.

### EyesSN_9: Camera field of view (Functional)
The new cameras must guarantee 170 deg as the FoV.

### EyesSN_10: Camera frame rate (Functional)
The new cameras must guarantee 30 fps.

## EyesSN_11: Onboard computational units (Container)

### EyesSN_12: GPU (Informational)
The head Mk 3 must mount NVidia Orin NX board to be used to acquire the video stream from cameras.

## EyesSN_13: Maintenance (Container)

### EyesSN_14: Ease of maintenance (Functional)
The eyes shall expose ease access to perform maintenance / repairments.
