# neck_functional_requirements

## NeckFR_1: Sensing (Container)

### NeckFR_2: Disambiguate kinematic configurations from sensor readings (Functional)
We shall be always able to reconstruct the kinematic configuration of the mechanism univocally.
This means that the sensors shall be mounted on the structure accordingly to provide suitable readings that help to disambiguate any possible configuration.
- Rationale: An example that we aim to prevent from striking and disrupting our efforts.
  - We use an absolute sensing system (e.g., AEA sensors)
  - However, the sensors may be subject to multiturns behaviors.
  - As a result, we lose the possibility to disambiguate kinematic configurations from the sensor readings.

### NeckFR_5: Vision Accuracy (Functional)
The absolute sensing must guarantee high accuracy of 3D reconstruction of the world through the vision system.
In particular, any possible impairment (e.g., backlash) must be measured and thus taken into account by the high-level vision algorithms.

### NeckFR_21: Absolute accurate encoders (Informational)
The joint angles shall be measured using absolute encoders equipped with the proper resolution to support control performances and vision accuracy.

## NeckFR_3: Kinematics (Container)

### NeckFR_4: Gazing for Grasping on a table (Functional)
The neck shall guarantee the functionalities required by a successful grasping action.
For verification purposes, one can refer to https://github.com/robotology/icub-gazebo-grasping-sandbox.

### NeckFR_7: Range of motion (Functional)
The range of motion of the neck shall not be lower than the current range.
- Pitch: [-45 22] deg
- Roll: [-20 20] deg
- Yaw: [-45 45] deg

### NeckFR_8: Degrees of Freedom (Informational)
The neck shall be endowed with 3 DoFs in this kinematic order:
1. Pitch
2. Roll
3. Yaw

### NeckFR_9: Reachable velocity (Functional)
We shall reach these peak velocities per joint:
- Pitch: 120 deg/s
- Roll: 120 deg/s
- Yaw: 120 deg/s
We shall reach these average velocities per joint:
- Pitch: 80 deg/s
- Roll: 80 deg/s
- Yaw: 80 deg/s
- Rationale: We determined these velocity bounds experimentally.
  See https://github.com/icub-tech-iit/study-icub-headedge/issues/30.

### NeckFR_19: Home Configuration aligned with Gravity (Functional)
In the home configuration where the joints are all zeroed, the head must be aligned along the gravity.

### NeckFR_20: Aid for absolute encoders alignment (Informational)
We shall provide a mechanism to support a precise alignment of the absolute encoders' readings with respect to the kinematics.
Possible solutions may include:
- pins
- collars

## NeckFR_6: Tendonless (Informational)
The mechanism shall be tendonless.

## NeckFR_10: Payload (Container)

### NeckFR_11: Current iCub head payload (Functional)
The current iCub head payload is handled as per requirements.

### NeckFR_12: Current ergoCub head payload (Functional)
The current ergoCub head payload is handled as per requirements.

### NeckFR_13: Fictitious head (Functional)
A payload weighing 1.1 times the ergoCub head is handled correctly.

## NeckFR_16: Dynamics (Container)

### NeckFR_17: Current Caps (Functional)
While operating at its maximum performance, the mechanism shall not exceed the current caps specified for the motors and the transmission.

### NeckFR_18: Torque Caps (Functional)
While operating at its maximum performance, the mechanism shall not exceed the torque caps specified for the motors and the transmission.

### NeckFR_14: Velocity Caps (Functional)
While operating at its maximum performance, the mechanism shall not exceed the velocity caps specified for the motors and the transmission.

## NeckFR_22: Safety (Container)

### NeckFR_23: Hard stops (Informational)
The mechanical structure shall foresee hard-stops.

## NeckFR_24: Robustness against disturbances (Container)

### NeckFR_25: Robustness against vibrations (Functional)
We shall guarantee that the neck is robust against the following external disturbances:
- 2 g at a period of 0.06 s applied to a direction parallel to the neck base.
- 3 g at a period of 0.06 s applied to a direction orthogonal to the neck base.
