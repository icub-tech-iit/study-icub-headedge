# neck_stakeholder_needs

## NeckSN_1: Robustness against disturbances (Container)
The neck shall be robust enough not to break or suffer from failures (snapped tendons) under several circumstances:
- walking.
- telepresence.
- flying (iRonCub).
- driving at higher speed (wheeled ergoCub).

### NeckSN_2: Robustness against "whiplash" (Functional)
"Whiplash" is a particular phenomenon that takes place when abrupt movements of the torso get amplified at the level of the neck.
One relevant example:
· during walking, one motor goes into hardware fault, the robot falls down (most of the time is attached to the crane) and the whiplash occurs.
https://github.com/icub-tech-iit/proto/issues/2717

### NeckSN_3: Robustness against vibrations (Functional)
During walking, the neck undergoes a significant level of vibrations.
We shall guarantee that the neck is robust enough against such vibrations.

## NeckSN_4: Payload (Functional)
We shall have some satefy margin on the payload.

### NeckSN_5: ergoCub with eyes (Functional)
It is convenient to have a suitable margin for future developments. For example, equipping the ergoCub head with moving eye bulbs.

### NeckSN_15: CPU in the torso (Informational)
Evaluate the possibility to move the COM-Express Type10 in the torso (iCub only).
- Rationale: This way we can make iCub head lighter.

### NeckSN_18: Standard payloads (Functional)
The neck shall be capable of driving the iCub head and the ergoCub head in their present configurations, plus the head 4K.

### NeckSN_22: Equipment (Informational)
The equipment available on the heads (iCub and ergoCub) must remain unvaried.
This means that, e.g., the speaker, the mic, the IMU available on the iCub head must stay available, although their mounting could undergo slight modifications.

## NeckSN_6: Aesthetics (Functional)
The neck shall fit well the size of the torso and the head.
Also, we shall remain as close as possible to the present configuration of the head in terms of, e.g., distances between the eyes and the neck base.

## NeckSN_7: Backdrivability (Functional)
The neck shall be as much backdrivable as possible.

## NeckSN_8: Kinematics (Container)

### NeckSN_11: Reachable velocity (Functional)
The angular velocity of the head (the payload of the neck) shall reach at least the same velocity currently attainable.

### NeckSN_9: Range of motion (Functional)
The range of motion of the neck shall not be lower than the current range.
- Pitch: [-45 22] deg
- Roll: [-20 20] deg
- Yaw: [-45 45] deg

### NeckSN_10: Degrees of Freedom (Informational)
The neck shall be endowed with 3 DoFs in this kinematic order:
1. Pitch
2. Roll
3. Yaw
This order is warmly recommended but not strictly mandatory. Any change in the order will impact the high-level software (aka gaze controller) and thus entails a careful review.

### NeckSN_12: Serial equivalence (Functional)
Whatever kinematic structure we will come up with, we shall guarantee that it is serializable, meaning there must exist an equivalent serial kinematic chain representing the entire set of attainable movements.
This need stems from the struggle we paid at the high level to deal with the torso and wrist mechanisms of R1, which were not serializable.
Remarkably, it was asked to apply the same requirement in the past to the development of the wrist-mk2.x of ergoCub.

## NeckSN_13: Maintenance (Container)

### NeckSN_14: Ease of maintenance (Functional)
The neck shall expose ease access to perform maintenance / repairments.

## NeckSN_16: Variants (Container)

### NeckSN_17: Tendonless serial mechanism (Informational)
The design process must consider a tendonless serial mechanism as a baseline.

## NeckSN_19: FT Sensing (Informational)
The neck shall be equipped with a 6-axis FT sensor.

## NeckSN_20: System (Container)

### NeckSN_21: Onboard Electronics (Functional)
The overall head system must be fully autonomous in terms of control electronics,: i.e., the control boards must be mounted in the head.

### NeckSN_23: New Electronics (Functional)
If possible and if the circumstances are favorable, we must consider using the new control boards (e.g., AMCBLDC, AMC) instead of the EMS, 2FOC.
- Rationale: The new control boards enable MBSE design.
